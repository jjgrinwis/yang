// our second vlan test. This time we want to work on a group of devices
// all members of a device are always in the <member> list.
// so if we're using just some devices or multiple groups within a group
// all members should be in the member leaf.
//
// root@ncs01:/opt/t-i.demo/extend-data-model# pyang -f tree vlan-new.yang 
// module: vlan-new
// augment /ncs:services:
//    +--rw vlan* [name]
//       +--rw name                        string
//       +--rw id?                         int16
//       +--rw device-group?               -> /ncs:devices/device-group/name
//
// vlan name is a key so always unique and we want id also to be unique.
//
module vlan-new {

  namespace "http://telindus.nl/yang/vlan-new";
  prefix vn;

  import tailf-ncs {
    prefix ncs;
  }

  import tailf-common {
    prefix tailf;
  }

  revision 2015-03-30 {
    description "Updated version with new YANG model";

  }

  augment /ncs:services {
    list vlan {
      tailf:info "add a vlan to set of devices";
      key name;
      unique id;

      uses ncs:service-data;
      ncs:servicepoint "vlan";

      leaf name {
        tailf:info "vlan name";
        type string {
          length "1..20";
        }
      }
      
      leaf id {
        tailf:info "vlan id";
        type int16 {
           range "1500..1600";
        }
      }

      leaf device-group {
        // let the customer select a device-group
        // all devices from this device-group should get the same vlan's.
        // XML template should use /devices/device/device-group/member to select all device members
        tailf:info "select device-group";
        type leafref {
          path "/ncs:devices/ncs:device-group/ncs:name";
        }
      }
    }
  }
}
